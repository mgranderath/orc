module openwrt-uci-extension {
    namespace "urn:jacobs:yang:openwrt-uci";
    prefix "ouci";

    contact "Malte Granderath <m.granderath@jacobs-university.de>";
    revision 2019-09-14 {
      description "initial revision";
    }

    extension package {
        argument name;
    }

    extension section {
        argument name;
    }

    extension option {
        argument name;
    }

    extension section-name {
        argument name;
    }

    extension leaf-as-name {
        argument name;
    }
}
